module acc-connection {
  yang-version 1.1;
  namespace "urn:ccsa:yang:acc-connection";
  prefix acc-con;

  import acc-devm {
    prefix acc-devm;
  }

  import acc-yang-types {
    prefix acc-type;
  }

  revision 2020-02-09 {
    description
      "move vlan-type, access-action from acc-eth";
  }

  typedef vlan-type {
    type enumeration {
      enum "c-tag" {
        value 0;
        description
          "c-tag";
      }
      enum "s-tag" {
        value 1;
        description
          "s-tag";
      }
      enum "un-tag" {
        value 2;
        description
          "no-tag";
      }
    }
    description
      "vlan type";
  }

  typedef access-action {
    type enumeration {
      enum "keep" {
        value 0;
        description
          "keep vlan";
      }
      enum "push_pop" {
        value 1;
        description
          "push-pop vlan";
      }
      enum "exchange" {
        value 2;
        description
          "exchange vlan";
      }
    }
    description
      "vlan access action";
  }

  grouping vlan-spec {
    leaf-list vlan-id {
      when "../vlan-type != 'un-tag'";
      type uint64 {
        range "1..4094";
      }
      min-elements 1;
    }

    leaf vlan-priority {
      when "../vlan-type != 'un-tag'";
      type uint64 {
        range "0..7";
      }
      description
        "default 0";
    }

    leaf access-action {
      type access-action;
    }

    leaf vlan-type {
      type vlan-type;
    }
  }

  grouping capacity {
    choice for-odu-or-eth {
      case for-odu-or-sdh {
        leaf total-size {
          type uint64;
          mandatory true;
          description
            "total size, When ODU,SDH,  mandatory must to be true and others must not exists";
        }
      }

      case for-eth-or-eos {
        leaf cir {
          type uint64;
          mandatory true;
          description
            "Important , When ETH,EOS   mandatory must to be true and total-size must not exists";
        }

        leaf pir {
          type uint64;
          description
            "Important , When ETH,EOS   mandatory must to be true and total-size must not exists";
        }

        leaf cbs {
          type uint64;
        }

        leaf pbs {
          type uint64;
        }
      }
    }
  }

  grouping connection {
    leaf name {
      type string;
      mandatory true;
      description
        "connection name must be unique in one device";
    }

    leaf label {
      type string;
      description
        "对于单独设备无意义，仅仅为网管上层串接端到端connection方便";
    }

    container state-pac {
      uses acc-devm:state-pac;
    }

    leaf layer-protocol-name {
      type identityref {
        base acc-type:layer-protocol-name;
      }
      mandatory true;
    }

    container requested-capacity {
      uses capacity;
    }

    leaf-list ctp {
      type string {
        length "1..64";
      }
      min-elements 2;
    }

    leaf service-type {
      type acc-devm:service-type;
      mandatory true;
    }

    leaf-list pg-id {
      type uint16;
      description
        "pg id";
    }
  }

  grouping create-connection {
    description
      "create connection";
    leaf label {
      type string;
      description
        "创建业务时不再下发name，由设备自己生成，可以下发这个新增的可选的label标识";
    }

    leaf service-type {
      type acc-devm:service-type;
      mandatory true;
    }

    leaf layer-protocol-name {
      type identityref {
        base acc-type:layer-protocol-name;
      }
      mandatory true;
    }

    container requested-capacity {
      uses capacity;
    }
  }

  container connections {
    description
      "connection container";
    list connection {
      key "name";
      description
        "connection list";
      uses connection;
    }
  }
}
