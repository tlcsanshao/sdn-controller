module acc-devm {
  yang-version 1.1;
  namespace "urn:ccsa:yang:acc-devm";
  prefix acc-devm;

  import ietf-yang-types {
    prefix yang;
  }

  import acc-yang-types {
    prefix acc-type;
  }

  import ietf-inet-types {
    prefix inet;
  }

  import acc-enum {
    prefix acc-eunm;
  }

  revision 2019-02-13;

  typedef operational-state {
    type enumeration {
      enum "up" {
        value 0;
      }
      enum "down" {
        value 1;
      }
    }
  }

  typedef admin-state {
    type enumeration {
      enum "enabled" {
        value 0;
      }
      enum "disabled" {
        value 1;
      }
    }
  }

  typedef laser-status {
    type enumeration {
      enum "laser-on" {
        value 0;
      }
      enum "laser-off" {
        value 1;
      }
      enum "no-optical-module" {
        value 2;
      }
    }
  }

  typedef loopback-type {
    type enumeration {
      enum "facility-loopback" {
        value 0;
      }
      enum "terminal-loopback" {
        value 1;
      }
      enum "non-loopback" {
        value 2;
      }
    }
  }

  typedef interface-type {
    type enumeration {
      enum "UNI" {
        value 0;
      }
      enum "NNI" {
        value 1;
      }
    }
  }

  typedef service-type {
    type enumeration {
      enum "ODU" {
        value 0;
      }
      enum "SDH" {
        value 1;
      }
      enum "EPL" {
        value 2;
      }
      enum "EVPL" {
        value 3;
      }
    }
  }

  typedef me-status {
    type enumeration {
      enum "installing" {
        value 0;
      }
      enum "running" {
        value 1;
      }
      enum "maintenance" {
        value 2;
      }
    }
  }

  typedef ntp-state {
    type enumeration {
      enum "NSET" {
        value 0;
      }
      enum "FSET" {
        value 1;
      }
      enum "SPIK" {
        value 2;
      }
      enum "FREQ" {
        value 3;
      }
      enum "SYNC" {
        value 4;
      }
    }
    description
      "rfc 5905：clock-never-set，freq-set-from-file，spike-detected，frequency-mode，clock-synchronized";
  }

  typedef reset-type {
    type enumeration {
      enum "soft-reset" {
        value 0;
      }
      enum "hard-reset" {
        value 1;
      }
    }
    description
      "soft-reset doesn't affect service";
  }

  typedef device-type {
    type enumeration {
      enum "otm-box" {
        value 0;
      }
      enum "po-box" {
        value 1;
      }
      enum "otm-pnp" {
        value 2;
      }
      enum "po-pnp" {
        value 3;
      }
    }
  }

  typedef port-role {
    type enumeration {
      enum "symmetric" {
        value 0;
      }
      enum "root" {
        value 1;
      }
      enum "leaf-node" {
        value 2;
      }
    }
  }

  typedef protect-role {
    type enumeration {
      enum "null" {
        value 0;
      }
      enum "protected" {
        value 1;
      }
      enum "primary" {
        value 2;
      }
      enum "secondary" {
        value 3;
      }
    }
  }

  typedef eq-type {
    type enumeration {
      enum "power" {
        value 0;
      }
      enum "fan" {
        value 1;
      }
      enum "service" {
        value 2;
      }
      enum "system-control" {
        value 3;
      }
      enum "cross-connect" {
        value 4;
      }
      enum "clock" {
        value 5;
      }
    }
  }

  grouping state-pac {
    leaf operational-state {
      type operational-state;
      config false;
      mandatory true;
    }

    leaf admin-state {
      type admin-state;
      mandatory true;
    }
  }

  grouping ftp {
    leaf name {
      type string {
        length "1..64";
      }
      mandatory true;
    }

    container state-pac {
      uses state-pac;
    }

    leaf layer-protocol-name {
      type identityref {
        base acc-type:layer-protocol-name;
      }
      mandatory true;
    }

    leaf-list client-ctp {
      type leafref {
        path "/acc-devm:ctps/acc-devm:ctp/acc-devm:name";
      }
    }

    leaf-list server-ctp {
      type leafref {
        path "/acc-devm:ctps/acc-devm:ctp/acc-devm:name";
      }
    }
  }

  grouping ctp {
    leaf name {
      type string {
        length "1..64";
      }
      mandatory true;
      description
        "Name of ctp";
    }

    container state-pac {
      description
        "State of ctp";
      uses state-pac;
    }

    leaf layer-protocol-name {
      type identityref {
        base acc-type:layer-protocol-name;
      }
      mandatory true;
    }

    leaf port-role {
      type port-role;
      default "symmetric";
      config false;
    }

    leaf protect-role {
      type protect-role;
      config false;
      mandatory true;
    }

    leaf server-tp {
      type string {
        length "1..64";
      }
      mandatory true;
      description
        "parent PTP name";
    }

    leaf loop-back {
      type loopback-type;
      mandatory true;
      description
        "Loop back type of ctp,default non-loopback";
    }
  }

  grouping mc-port {
    leaf name {
      type string;
      mandatory true;
      description
        "命名规则：端口类型加序号，如：RJ45_1, USB_1, Serial_1";
    }

    leaf mac-address {
      type string;
      config false;
    }

    leaf operational-state {
      type operational-state;
      config false;
      mandatory true;
    }

    leaf admin-state {
      type admin-state;
      mandatory true;
    }
  }

  container me {
    leaf name {
      type string {
        length "1..64";
      }
      mandatory true;
      description
        "for UMS, it's a label";
    }

    leaf uuid {
      type string;
      config false;
      mandatory true;
      description
        "Universal unique identifier, MAC address is suggested. for UMS,it's real name";
    }

    leaf status {
      type me-status;
      mandatory true;
    }

    leaf manufacturer {
      type string {
        length "1..32";
      }
      config false;
      mandatory true;
      description
        "Manufacturer";
    }

    leaf product-name {
      type string {
        length "1..32";
      }
      config false;
      mandatory true;
      description
        "Product name";
    }

    leaf software-version {
      type string {
        length "1..32";
      }
      config false;
      mandatory true;
      description
        "Software version";
    }

    leaf hardware-version {
      type string {
        length "1..64";
      }
      config false;
      mandatory true;
      description
        "Hardware version";
    }

    leaf device-type {
      type device-type;
      config false;
      mandatory true;
      description
        "Device type";
    }

    leaf-list layer-protocol-name {
      type identityref {
        base acc-type:layer-protocol-name;
      }
      config false;
      min-elements 1;
      description
        "Layer protocol name";
    }

    leaf ip-address {
      type inet:ipv4-address;
      mandatory true;
      description
        "Ip address(ipv4)";
    }

    leaf mask {
      type yang:dotted-quad;
      mandatory true;
      description
        "Mask";
    }

    leaf ntp-enable {
      type boolean;
      mandatory true;
      description
        "Support ntp or not.";
    }

    leaf ntp-state {
      type ntp-state;
      config false;
      description
        "ntpState提到这里，当ntpEnable使能后,代表网元与ntpServer同步的最终结果";
    }

    leaf ntp-server-in-use {
      type string {
        length "1..32";
      }
      config false;
      description
        "ntpServer name";
    }

    container ntp-servers {
      list ntp-server {
        key "name";
        leaf name {
          type string {
            length "1..32";
          }
          description
            "Name of ntp server.";
        }

        leaf ip-address {
          type inet:ipv4-address;
          mandatory true;
          description
            "Ip address of ntp";
        }

        leaf port {
          type inet:port-number;
          default "123";
          description
            "Port number of ntp";
        }

        leaf ntp-version {
          type string {
            length "1..64";
          }
          description
            "Ntp version default value: V3";
        }
      }
    }

    leaf gate-way1 {
      type inet:ipv4-address;
      mandatory true;
      description
        "Gat way1(ipv4)";
    }

    leaf gate-way2 {
      type inet:ipv4-address;
      description
        "Gat way2(ipv4)";
    }

    leaf-list eq {
      type leafref {
        path "/acc-devm:eqs/acc-devm:eq/acc-devm:name";
      }
      config false;
      min-elements 1;
      description
        "Eq list";
    }

    leaf-list mc-port {
      type leafref {
        path "/acc-devm:mc-ports/acc-devm:mc-port/acc-devm:name";
      }
      config false;
      min-elements 1;
    }
  }

  container ptps {
    list ptp {
      key "name";
      min-elements 1;
      leaf name {
        type string {
          length "1..64";
        }
        description
          "Name of ptp";
      }

      container state-pac {
        description
          "State of ptp";
        uses state-pac;
      }

      leaf layer-protocol-name {
        type identityref {
          base acc-type:layer-protocol-name;
        }
        mandatory true;
        description
          "current protocol setting value";
      }

      leaf-list supported-layer-protocol-name {
        type identityref {
          base acc-type:layer-protocol-name;
        }
        config false;
        description
          "all supported abilities of protocol";
      }

      leaf peer-ip-address {
        type string {
          length "1..16";
        }
        config false;
        description
          "Peer ip address";
      }

      leaf peer-tcp-id {
        type string {
          length "1..64";
        }
        config false;
        description
          "Peer ptp tcp-id";
      }

      leaf local-tcp-id {
        type string {
          length "1..64";
        }
        config false;
        description
          "Local ptp tcp-id";
      }

      leaf laser-status {
        type laser-status;
        mandatory true;
        description
          "Laser status of ptp,default laser-on";
      }

      leaf-list ctp {
        type leafref {
          path "/acc-devm:ctps/acc-devm:ctp/acc-devm:name";
        }
        description
          "Ctp list";
      }

      leaf interface-type {
        type interface-type;
        mandatory true;
        description
          "Interface type of ptp";
      }

      leaf loop-back {
        type loopback-type;
        mandatory true;
        description
          "Loop back type of ptp,default non-loopback";
      }

      leaf-list remote-ptp {
        type leafref {
          path "/acc-devm:ptps/acc-devm:ptp/acc-devm:name";
        }
        config false;
      }

      container optical-power-pac {
        leaf input-power {
          type acc-type:real;
          config false;
          mandatory true;
          description
            "Input power of ptp";
        }

        leaf output-power {
          type acc-type:real;
          mandatory true;
          description
            "Output power of ptp";
        }

        leaf input-power-upper-threshold {
          type acc-type:real;
          config false;
          mandatory true;
          description
            "Input power upper threshold of ptp";
        }

        leaf input-power-lower-threshold {
          type acc-type:real;
          config false;
          mandatory true;
          description
            "Input power lower threshold of ptp";
        }
      }
    }
  }

  container ftps {
    list ftp {
      key "name";
      uses ftp;
    }
  }

  container ctps {
    list ctp {
      key "name";
      uses ctp;
    }
  }

  container mc-ports {
    list mc-port {
      key "name";
      uses mc-port;
    }
  }

  container eqs {
    list eq {
      key "name";
      min-elements 1;
      leaf name {
        type string {
          length "1..64";
        }
      }

      leaf plug-state {
        type boolean;
        config false;
        mandatory true;
      }

      leaf-list eq-type {
        type eq-type;
        config false;
        min-elements 1;
      }

      leaf software-version {
        type string {
          length "1..32";
        }
        config false;
      }

      leaf hardware-version {
        type string {
          length "1..32";
        }
        config false;
      }

      leaf-list ptp {
        type leafref {
          path "/acc-devm:ptps/acc-devm:ptp/acc-devm:name";
        }
        config false;
      }

      leaf-list ftp {
        type leafref {
          path "/acc-devm:ptps/acc-devm:ptp/acc-devm:name";
        }
        config false;
      }
    }
  }

  rpc reset {
    input {
      leaf eq-name {
        type string {
          length "1..64";
        }
        mandatory true;
      }

      leaf reset-type {
        type reset-type;
        mandatory true;
      }
    }
  }

  rpc modify-user-password {
    input {
      leaf user-name {
        type string;
        description
          "可选，默认当前用户";
      }

      leaf old-password {
        type string {
          length "8..16";
        }
        mandatory true;
      }

      leaf new-password {
        type string {
          length "8..16";
        }
        mandatory true;
      }
    }
  }

  rpc set-managed-element-time {
    input {
      leaf new-time {
        type yang:date-and-time;
        mandatory true;
      }
    }
  }

  rpc get-managed-element-time {

    output {
      leaf date-time {
        type yang:date-and-time;
        mandatory true;
      }
    }
  }

  notification peer-change-notification {
    leaf ptp-name {
      type string {
        length "1..64";
      }
      mandatory true;
    }

    leaf peer-ip-address {
      type string {
        length "1..16";
      }
      mandatory true;
    }

    leaf peer-ptp-tcp-id {
      type string {
        length "1..64";
      }
      mandatory true;
    }
  }
}
