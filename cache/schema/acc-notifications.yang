module acc-notifications {
  yang-version 1.1;
  namespace "urn:ccsa:yang:acc-notifications";
  prefix acc-ntf;

  typedef event-type {
    type enumeration {
      enum "object-creation" {
        value 0;
      }
      enum "object-deletion" {
        value 1;
      }
      enum "attribute-value-change" {
        value 2;
      }
      enum "user-login" {
        value 3;
      }
      enum "user-logoff" {
        value 4;
      }
    }
  }

  grouping event {
    leaf event-serial-no {
      type uint64;
      mandatory true;
    }

    leaf event-type {
      type event-type;
      mandatory true;
    }

    leaf object-name {
      type string;
      mandatory true;
    }

    leaf object-type {
      type string;
      mandatory true;
    }

    leaf user-name {
      type string;
    }
  }

  notification common-notification {
    container event {
      uses event;
    }
  }

  notification attribute-value-change-notification {
    container event {
      uses event;
    }

    container attribute-value-change {
      leaf attribute-name {
        type string;
        mandatory true;
      }

      leaf new-value {
        type string;
        mandatory true;
      }

      leaf old-value {
        type string;
      }
    }
  }
}
